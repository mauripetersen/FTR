Attribute VB_Name = "ModDWG_2_SVG"
Public Function Hex2(n As Long) As String
    Hex2 = Right("00" & Hex(n), 2)
End Function



Public Function get_selected_objects() As Collection
    Dim selectedObjs As Collection
    Set selectedObjs = New Collection
    
    If ThisDrawing.PickfirstSelectionSet.Count > 0 Then
        For Each selectedObj In ThisDrawing.PickfirstSelectionSet
            selectedObjs.Add selectedObj
        Next selectedObj
    End If
    
    Set get_selected_objects = selectedObjs
End Function



Public Sub dwg_2_svg()
    Dim selectedObj As Object
    
    If ThisDrawing.PickfirstSelectionSet.Count > 0 Then
        Dim selectedObjs As Collection
        Set selectedObjs = get_selected_objects()
        
        Dim output_path As String
        output_path = "../create_svg.py"
        
        Dim pt As AcadPoint
        Dim line As AcadLine
        Dim poly As AcadLWPolyline
        Dim my_circle As AcadCircle
        
        Dim x1 As String, y1 As String, x2 As String, y2 As String
        Dim pt1 As Variant, pt2 As Variant, coords As Variant
        Dim ptc As Variant, r As Double
        Dim d As String
        
        Dim clr As AcadAcCmColor
        Dim hex_clr As String
        
        Dim codeBackground As String
        Dim circlesColl As Collection
        Dim pathsColl As Collection
        Dim linesColl As Collection
        
        Set circlesColl = New Collection
        Set pathsColl = New Collection
        Set linesColl = New Collection
        
        AppActivate ThisDrawing.Application.Caption
        
        On Error Resume Next
        Dim winPt1 As Variant, winPt2 As Variant
        winPt1 = ThisDrawing.Utility.GetPoint(, "First window point (Bottom Left): ")
        winPt2 = ThisDrawing.Utility.GetPoint(, "Second window point (Top Right): ")
        
        If Err.Number <> 0 Then
            Err.Clear
            Exit Sub
        End If
        On Error GoTo 0
        
        Dim wx1 As Double, wy1 As Double, wx2 As Double, wy2 As Double, wi As Integer, he As Integer
        wx1 = winPt1(0)
        wy1 = winPt1(1)
        wx2 = winPt2(0)
        wy2 = winPt2(1)
        wi = CInt(wx2 - wx1)
        he = CInt(wy2 - wy1)
        
        For Each selectedObj In selectedObjs
            If selectedObj.Layer = "background" Then
                Set clr = selectedObj.TrueColor
                hex_clr = "#" & Hex2(clr.Red) & Hex2(clr.Green) & Hex2(clr.Blue)
                
                codeBackground = "dwg.add(dwg.rect(insert=(0, 0), size=('100%', '100%'), fill='" & hex_clr & "'))"
            ElseIf selectedObj.Layer <> "0" Then
                If TypeOf selectedObj Is AcadPoint Then
                    Set pt = selectedObj
                    coords = pt.Coordinates
                    
                    x1 = Replace(Round(coords(0) - wx1, 3), ",", ".")
                    y1 = Replace(Round(he - (coords(1) - wy1), 3), ",", ".")
                    
                    Set clr = selectedObj.TrueColor
                    hex_clr = "#" & Hex2(clr.Red) & Hex2(clr.Green) & Hex2(clr.Blue)
                    
                    circlesColl.Add "dwg.add(dwg.circle(center=(" & x1 & ", " & y1 & "), r=90, fill='none', stroke='" & hex_clr & "', stroke_width=40))"
                    circlesColl.Add "dwg.add(dwg.circle(center=(" & x1 & ", " & y1 & "), r=30, fill='" & hex_clr & "', stroke='" & hex_clr & "', stroke_width=0))"
                ElseIf TypeOf selectedObj Is AcadLine Then
                    Set line = selectedObj
                    pt1 = line.StartPoint
                    pt2 = line.EndPoint
                    
                    x1 = Replace(Round(pt1(0) - wx1, 3), ",", ".")
                    y1 = Replace(Round(he - (pt1(1) - wy1), 3), ",", ".")
                    x2 = Replace(Round(pt2(0) - wx1, 3), ",", ".")
                    y2 = Replace(Round(he - (pt2(1) - wy1), 3), ",", ".")
                    
                    Set clr = selectedObj.TrueColor
                    hex_clr = "#" & Hex2(clr.Red) & Hex2(clr.Green) & Hex2(clr.Blue)
                    
                    linesColl.Add "dwg.add(dwg.line(start=(" & x1 & ", " & y1 & "), end=(" & x2 & ", " & y2 & "), stroke='" & hex_clr & "', stroke_width='" & selectedObj.Layer & "'))"
                ElseIf TypeOf selectedObj Is AcadLWPolyline Then
                    Set poly = selectedObj
                    coords = poly.Coordinates
                    
                    d = "'M"
                    For k = LBound(coords) To UBound(coords) Step 2
                        x1 = Replace(Round(coords(k) - wx1, 3), ",", ".")
                        y1 = Replace(Round(he - (coords(k + 1) - wy1), 3), ",", ".")
                        
                        d = d & x1 & "," & y1 & " "
                    Next k
                    d = d & "Z'"
                    
                    Set clr = selectedObj.TrueColor
                    hex_clr = "#" & Hex2(clr.Red) & Hex2(clr.Green) & Hex2(clr.Blue)
                    
                    pathsColl.Add "dwg.add(dwg.path(d=" & d & ", stroke='" & hex_clr & "', fill='none', stroke_width='" & selectedObj.Layer & "'))"
                ElseIf TypeOf selectedObj Is AcadCircle Then
                    Set my_circle = selectedObj
                    ptc = my_circle.Center
                    
                    x1 = Replace(Round(ptc(0) - wx1, 3), ",", ".")
                    y1 = Replace(Round(he - (ptc(1) - wy1), 3), ",", ".")
                    r = Replace(Round(my_circle.Radius, 3), ",", ".")
                    
                    Set clr = selectedObj.TrueColor
                    hex_clr = "#" & Hex2(clr.Red) & Hex2(clr.Green) & Hex2(clr.Blue)
                    
                    circlesColl.Add "dwg.add(dwg.circle(center=(" & x1 & ", " & y1 & "), r=" & r & ", fill='none', stroke='" & hex_clr & "', stroke_width='" & selectedObj.Layer & "'))"
                End If
            End If
        Next selectedObj
        
        Open output_path For Output As 1
            Print #1, "import svgwrite"
            Print #1, ""
            Print #1, "dwg = svgwrite.Drawing('logo.svg', size=('" & wi & "', '" & he & "'))"
            If codeBackground <> "" Then
                Print #1, codeBackground
            End If
            Print #1, ""
            
            For Each cc In circlesColl
                Print #1, cc
            Next cc
            Print #1, ""
            For Each pc In pathsColl
                Print #1, pc
            Next pc
            Print #1, ""
            For Each lc In linesColl
                Print #1, lc
            Next lc
            
            Print #1, ""
            Print #1, "dwg.save()"
        Close #1
        
        MsgBox "Done."
    End If
End Sub
